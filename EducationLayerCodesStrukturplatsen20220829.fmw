FME workspace EducationLayerCodesStrukturplatsen20220829.fmw

Parameters:
- DestDataset_TEXTLINE =
- FEATURE_TYPES =
- FEATURE_TYPES_2 =
- FEATURE_TYPES_3 =
- SourceDataset_SHAREPOINT =
- SourceDataset_SHAREPOINT_4 =
- SourceDataset_SHAREPOINT_5 =

Readers:
- SHAREPOINT_1: SHAREPOINT from $(SourceDataset_SHAREPOINT)
- SHAREPOINT_2: SHAREPOINT from $(SourceDataset_SHAREPOINT_5)
- SHAREPOINT_3: SHAREPOINT from $(SourceDataset_SHAREPOINT_4)

Writers:
- TEXTLINE_1: TEXTLINE to $(DestDataset_TEXTLINE)

Kodlista SB11 (reader SHAREPOINT_1)
    attributes: Kod Computed, Ändrat DateTime, Skapad DateTime, Beskrivning Text, Kommentar Note, Ersatt av Text, Kodstatus Choice, Elementtyp Choice, Attribut Choice, GRUPP Choice, Skapad av User, Ändrat av User
    -> Tester_2
Tester_2
    BOOL_OP = AND
    COMPOSITE_TEST = 1 AND 2
    TEST_CLAUSE:
      TEST @Value(Kodstatus) NOT_= 90 - Använd ej
      TEST @Value(Kod) NOT_= ------
    TEST_MODE = TEST
    PASSED -> AttributeCreator
AttributeCreator
    ATTR_TABLE:
      SET_TO parent
      SET_TO id
    -> TestFilter
Note: Hantera element från strukturplatsen
TestFilter
    DEFAULT_VALUE = <UNFILTERED>
    TEST_LIST = "BOOL_OP,OR,COMPOSITE_TEST,""""""1"""""",TEST_CLAUSE,TEST @Value(Elementtyp) = Landskapsinformation",@Value(Elementtyp) = Landskapsinformation,"BOOL_OP,OR,COMPOSITE_TEST,""""""1"""""",TEST_CLAUSE,TEST @Value(Elementtyp) = Byggdelar",@Value(Elementtyp) = Byggdelar,"BOOL_OP,OR,COMPOSITE_TEST,""""""1"""""",TEST_CLAUSE,TEST @Value(Elementtyp) = Alternativtabell",@Value(Elementtyp) = Alternativtabell
    @Value(Elementtyp) = Landskapsinformation -> AttributeCreator_7
    @Value(Elementtyp) = Byggdelar -> AttributeCreator_8
    @Value(Elementtyp) = Alternativtabell -> AttributeCreator_7
    <UNFILTERED> -> TestFilter_2
AttributeCreator_7
    ATTR_TABLE = SET_TO Typ = Element
    -> AttributeManager_2
Note: Här rättas några värden
AttributeManager_2
    ATTR_TABLE = SET_TO GRUPP = FME_CONDITIONAL:DEFAULT_VALUE'_FME_NO_OP_'BOOL_OP;OR;COMPOSITE_TEST;1;CASE_INSENSITIVE_TEST @Value(Kod) BEGINS_WITH MLJ'_MLJ - Miljö'BOOL_OP;OR;COMPOSITE_TEST;1;TEST @Value(Attribut) = Tabell 4.56a Utrymme'xU Utrymmen (SB11)'FME_NUM_CONDITIONS3___
    -> AttributeCreator_3
    -> DuplicateFilter
Note: Tar bort dubletter och skapar en rad för att beskriva övre nivåer (dessa övre nivåer finns inte i strukturplatsen som rader). här blir det ett par extra rader skapade helt enkelt som sammanförs med befintliga rader
DuplicateFilter
    INPUT_ORDERED_CHOICE = No
    KEYATTR = GRUPP
    UNIQUE -> AttributeManager
AttributeManager
    ATTR_TABLE:
      SET_TO parent = FME_CONDITIONAL:DEFAULT_VALUE'_FME_NO_OP_'BOOL_OP;OR;COMPOSITE_TEST;1;TEST @Value(Elementtyp) = Alternativtabell'Alternativtabell'BOOL_OP;OR;COMPOSITE_TEST;1;TEST @Value(Elementtyp) = Landskapsinformation'Landskapsinformation'BOOL_OP;OR;COMPOSITE_TEST;1;TEST @Value(Elementtyp) =  Byggdelar'Byggdelar'FME_NUM_CONDITIONS4___
      SET_TO id = @Value(GRUPP)
      SET_TO Beskrivning = FME_NULL_VALUE
      SET_TO text = @Value(GRUPP)
    -> Junction
Note: Skriv grupp som parent på allt. Skrivs över där det behövs senare. De övre nivåerna får en parent på detta vis
AttributeCreator_3
    ATTR_TABLE:
      SET_TO id = @Value(Kod)
      SET_TO parent = @Value(GRUPP)
      SET_TO text = @Value(Kod)
    -> Junction
Junction
    -> StringReplacer_2
StringReplacer_2
    CASE = NO
    FIND_TEXT = /
    NO_MATCH = _FME_NO_OP_
    REGEXP = NO
    SRC_ATTRS = id,parent
    -> StringReplacer_3
StringReplacer_3
    CASE = NO
    FIND_TEXT = ,
    NO_MATCH = _FME_NO_OP_
    REGEXP = NO
    SRC_ATTRS = id,parent
    -> StringReplacer
StringReplacer
    CASE = NO
    FIND_TEXT = " "
    NO_MATCH = _FME_NO_OP_
    REGEXP = NO
    REPLACE_TEXT = _
    SRC_ATTRS = id,parent
    -> StringReplacer_4
StringReplacer_4
    CASE = NO
    FIND_TEXT = " "
    NO_MATCH = _FME_NO_OP_
    REGEXP = NO
    REPLACE_TEXT = _
    SRC_ATTRS = id,parent
    -> StringReplacer_5
StringReplacer_5
    CASE = NO
    FIND_TEXT = (
    NO_MATCH = _FME_NO_OP_
    REGEXP = NO
    SRC_ATTRS = id,parent
    -> StringReplacer_6
StringReplacer_6
    CASE = NO
    FIND_TEXT = )
    NO_MATCH = _FME_NO_OP_
    REGEXP = NO
    SRC_ATTRS = id,parent
    -> Junction_2
AttributeCreator_8
    ATTR_TABLE = SET_TO Typ = Element
    -> AttributeCreator_4
Note: Man skulle kunna använda regex för att hitta första tecken framför -tecken .(?=-)(?<!-)
Note: id,kod behöver vara samma för JStree. En för länkning, en för visning
AttributeCreator_4
    ATTR_TABLE:
      SET_TO id = @Value(Kod)
      SET_TO text = @Value(Kod)
    -> StringReplacer_9
StringReplacer_9
    CASE = NO
    FIND_TEXT = -
    NO_MATCH = _FME_NO_OP_
    REGEXP = NO
    SRC_ATTRS = Kod
    -> StringLengthCalculator
StringLengthCalculator
    LENGTH_ATTR = _length
    SRC_ATTR = Kod
    -> SubstringExtractor
SubstringExtractor
    END = -2
    RESULT_ATTR = _substring
    SRC_STRING = @Value(Kod)
    START = 0
    -> StringPadder
StringPadder
    BLANK_ATTRIBUTE = Yes
    PADCHAR = -
    SIDE = Right
    SRC_ATTRS = _substring
    WIDTH = 6
    -> AttributeCreator_5
AttributeCreator_5
    ATTR_TABLE = SET_TO parent = @Value(_substring)
    -> StringReplacer_10
StringReplacer_10
    CASE = NO
    FIND_TEXT = ------
    NO_MATCH = _FME_NO_OP_
    REGEXP = YES
    REPLACE_TEXT = Byggdelar
    SRC_ATTRS = parent
    -> FeatureMerger [SUPPLIER]
    -> FeatureMerger [REQUESTOR]
FeatureMerger
    ATTR_ACCUM_MODE = Merge Supplier
    ATTR_CONFLICT_RES = Use Requestor
    IGNORE_NULLS = No
    JOIN_KEYS = @Value(parent) @Value(id) AUTO
    MERGE_TYPE = Attributes Only
    PROCESS_DUPS = NO
    REJECT_NULL_MISSING_KEYS = No
    SUPPLIERS_FIRST = No
    MERGED -> Junction_3
    UNMERGED_REQUESTOR -> Tester_3
Tester_3
    BOOL_OP = OR
    COMPOSITE_TEST = 1
    TEST_CLAUSE = CASE_INSENSITIVE_TEST @Value(id) NOT_CONTAINS -
    TEST_MODE = CASE_INSENSITIVE_TEST
    PASSED -> SubstringExtractor_2
    FAILED -> Junction_3
SubstringExtractor_2
    END = -3
    RESULT_ATTR = _substring
    SRC_STRING = @Value(Kod)
    START = 0
    -> StringPadder_2
StringPadder_2
    BLANK_ATTRIBUTE = Yes
    PADCHAR = -
    SIDE = Right
    SRC_ATTRS = _substring
    WIDTH = 6
    -> AttributeCreator_6
AttributeCreator_6
    ATTR_TABLE = SET_TO parent = @Value(_substring)
    -> Junction_3
Note: Hantera allt annat från strukturplatsen
TestFilter_2
    DEFAULT_VALUE = <UNFILTERED>
    TEST_LIST = "BOOL_OP,OR,COMPOSITE_TEST,""""""1"""""",TEST_CLAUSE,CASE_INSENSITIVE_TEST @Value(Attribut) = Ansvarig Part",@Value(Attribut) = Ansvarig Part,"BOOL_OP,OR,COMPOSITE_TEST,""""""1"""""",TEST_CLAUSE,CASE_INSENSITIVE_TEST @Value(Attribut) = Presentation",@Value(Attribut) = Presentation,"BOOL_OP,OR,COMPOSITE_TEST,""""""1"""""",TEST_CLAUSE,CASE_INSENSITIVE_TEST @Value(Attribut) = Status",@Value(Attribut) = Status
    @Value(Attribut) = Ansvarig Part -> JSONTemplater_2 [FEATURE]
    @Value(Attribut) = Presentation -> JSONTemplater_3 [FEATURE]
    @Value(Attribut) = Status -> JSONTemplater_4 [FEATURE]
DuplicateFilter_2
    INPUT_ORDERED_CHOICE = No
    KEYATTR = typtabell
    UNIQUE -> AttributeManager_3
AttributeManager_3
    ATTR_TABLE:
      RENAME_SET_VALUE kod > id = @Value(typtabell)
      SET_TO text = @Value(typtabell)
      SET_TO beskrivning > Beskrivning =
      SET_TO parent = #
TS_KODER_TYP (reader SHAREPOINT_2)
    attributes: kod Text, beskrivning Text, typtabell Text
    -> AttributeManager_4
AttributeManager_4
    ATTR_TABLE:
      RENAME_SET_VALUE kod > id
      SET_TO text = @Value(id)
      RENAME_SET_VALUE beskrivning > Beskrivning
      SET_TO parent = @Value(typtabell)
    -> JSONTemplater_5 [FEATURE]
Delområden och anläggningsdelar (reader SHAREPOINT_3)
    attributes: Status Choice, Delområde Choice, Anläggningsdel Computed, Beskrivning Text, Anmärkning Note, Vägnr MultiChoice, Placeringskod Text, Tidigare Namn Text, Får användas för komponentid Boolean, Anlaggningsdelsid Calculated
    -> JSONTemplater_6 [FEATURE]
Creator_7
    GEOMTYPE = Geometry Object
    NUM = 1
    CREATED -> JSONTemplater_2 [ROOT]
JSONTemplater_2
    FEATURE_QUERY_EXPR:
      {
      "Kod" : fme:get-attribute("Kod"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter_2
JSONFormatter_2
    ERROR_LIST_ATTR = _json_error
    FORMAT = Linearize
    JSON_DOCUMENT = @Value(_result)
    OUTPUT_ATTR = _ansvarigPart
    OUTPUT_ENCODING = UTF-8
    READ_FROM_FILE = NO
    REMOVE_EMPTY_OBJECTS_AND_ARRAYS = No
    REMOVE_EMPTY_STRINGS = No
    REMOVE_NULLS = No
    -> StringConcatenator_4
StringConcatenator_4
    ACTION = Create New Attribute
    PARM_LINE = fme_basicstring:24%21%2:var ansvarigpartjson = '@Value(_ansvarigPart)'
    VAL_ATTR = _result
    -> Aggregator
Creator_8
    GEOMTYPE = Geometry Object
    NUM = 1
    CREATED -> JSONTemplater_3 [ROOT]
JSONTemplater_3
    FEATURE_QUERY_EXPR:
      {
      "Kod" : fme:get-attribute("Kod"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter_3
JSONFormatter_3
    ERROR_LIST_ATTR = _json_error
    FORMAT = Linearize
    JSON_DOCUMENT = @Value(_result)
    OUTPUT_ATTR = _presentation
    OUTPUT_ENCODING = UTF-8
    READ_FROM_FILE = NO
    REMOVE_EMPTY_OBJECTS_AND_ARRAYS = No
    REMOVE_EMPTY_STRINGS = No
    REMOVE_NULLS = No
    -> StringConcatenator_3
StringConcatenator_3
    ACTION = Create New Attribute
    PARM_LINE = fme_basicstring:24%21%2:var presentationjson = '@Value(_presentation)'
    VAL_ATTR = _result
    -> Aggregator
Creator_9
    GEOMTYPE = Geometry Object
    NUM = 1
    CREATED -> JSONTemplater_4 [ROOT]
JSONTemplater_4
    FEATURE_QUERY_EXPR:
      {
      "Kod" : fme:get-attribute("Kod"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter_4
JSONFormatter_4
    ERROR_LIST_ATTR = _json_error
    FORMAT = Linearize
    JSON_DOCUMENT = @Value(_result)
    OUTPUT_ATTR = _status
    OUTPUT_ENCODING = UTF-8
    READ_FROM_FILE = NO
    REMOVE_EMPTY_OBJECTS_AND_ARRAYS = No
    REMOVE_EMPTY_STRINGS = No
    REMOVE_NULLS = No
    -> StringConcatenator_2
StringConcatenator_2
    ACTION = Create New Attribute
    PARM_LINE = "var statusjson = '@Value(_status)'\n"
    VAL_ATTR = _result
    -> Aggregator
Creator_11
    GEOMTYPE = Geometry Object
    NUM = 1
    CREATED -> JSONTemplater_5 [ROOT]
JSONTemplater_5
    FEATURE_QUERY_EXPR:
      {
      "id" : fme:get-attribute("id"),
      "parent" : fme:get-attribute("parent"),
      "text" : fme:get-attribute("text"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter_5
JSONFormatter_5
    ERROR_LIST_ATTR = _json_error
    FORMAT = Linearize
    JSON_DOCUMENT = @Value(_result)
    OUTPUT_ATTR = _typ
    OUTPUT_ENCODING = UTF-8
    READ_FROM_FILE = NO
    REMOVE_EMPTY_OBJECTS_AND_ARRAYS = No
    REMOVE_EMPTY_STRINGS = No
    REMOVE_NULLS = No
    -> StringConcatenator_7
StringConcatenator_7
    ACTION = Create New Attribute
    PARM_LINE = "var typjson = @Value(_typ)\n"
    VAL_ATTR = _result
    -> Aggregator
Creator_12
    GEOMTYPE = Geometry Object
    NUM = 1
    CREATED -> JSONTemplater_6 [ROOT]
JSONTemplater_6
    FEATURE_QUERY_EXPR:
      {
      "Kod" : fme:get-attribute("Anlaggningsdelsid"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter_6
JSONFormatter_6
    ERROR_LIST_ATTR = _json_error
    FORMAT = Linearize
    JSON_DOCUMENT = @Value(_result)
    OUTPUT_ATTR = _anlaggningsdelar
    OUTPUT_ENCODING = UTF-8
    READ_FROM_FILE = NO
    REMOVE_EMPTY_OBJECTS_AND_ARRAYS = No
    REMOVE_EMPTY_STRINGS = No
    REMOVE_NULLS = No
    -> StringConcatenator_8
StringConcatenator_8
    ACTION = Create New Attribute
    PARM_LINE = fme_basicstring:28%25%2:var anlaggningsdelarjson = '@Value(_anlaggningsdelar)'
    VAL_ATTR = _result
    -> Aggregator
Creator
    GEOMTYPE = Geometry Object
    NUM = 1
    CREATED -> rootLandskap
rootLandskap: AttributeCreator
    ATTR_TABLE:
      SET_TO id = Landskapsinformation
      SET_TO parent = #
      SET_TO text = Landskapsinformation
      SET_TO Beskrivning = Used when Byggdelar can't explain existing information
    -> Junction_2
Creator_2
    GEOMTYPE = Geometry Object
    NUM = 1
    CREATED -> rootAlternativ
rootAlternativ: AttributeCreator
    ATTR_TABLE:
      SET_TO id = Alternativtabell
      SET_TO parent = #
      SET_TO text = Alternativtabell
      SET_TO Beskrivning = Alternativa tabeller enligt SB11
    -> Junction_2
Creator_3
    GEOMTYPE = Geometry Object
    NUM = 1
    CREATED -> rootNoElement
rootNoElement: AttributeCreator
    ATTR_TABLE:
      SET_TO id = ------
      SET_TO parent = #
      SET_TO text = ------
      SET_TO Beskrivning = No element, for ex drawing help layers
    -> Junction_2
Creator_4
    GEOMTYPE = Geometry Object
    NUM = 1
    CREATED -> rootByggdelar
rootByggdelar: AttributeCreator
    ATTR_TABLE:
      SET_TO id = Byggdelar
      SET_TO parent = #
      SET_TO text = Byggdelar
      SET_TO Beskrivning = Byggdelar enligt BSAB96
    -> Junction_2
Junction_2
    -> Junction_3
Junction_3
    -> JSONTemplater [FEATURE]
Creator_5
    GEOMTYPE = Geometry Object
    NUM = 1
    CREATED -> JSONTemplater [ROOT]
JSONTemplater
    FEATURE_QUERY_EXPR:
      {
      "id" : fme:get-attribute("id"),
      "parent" : fme:get-attribute("parent"),
      "text" : fme:get-attribute("text"),
      "Beskrivning" : fme:get-attribute("Beskrivning")
      }
    RESULT_ATTRIBUTE = _result
    ROOT_QUERY_EXPR = "[\nfme:process-features(\"FEATURE\")\n]\n\n"
    VISIBLE_QUERY_VALIDATE = No
    -> JSONFormatter
JSONFormatter
    ERROR_LIST_ATTR = _json_error
    FORMAT = Linearize
    JSON_DOCUMENT = @Value(_result)
    OUTPUT_ATTR = _element
    OUTPUT_ENCODING = UTF-8
    READ_FROM_FILE = NO
    REMOVE_EMPTY_OBJECTS_AND_ARRAYS = No
    REMOVE_EMPTY_STRINGS = No
    REMOVE_NULLS = No
    -> StringConcatenator
StringConcatenator
    ACTION = Create New Attribute
    PARM_LINE = fme_basicstring:14%16%1:var element = @Value(_element)
    VAL_ATTR = _result
    -> Aggregator
Aggregator
    ACCUM_ATTRS_NAME = Merge Incoming Attributes
    AGGREGATE_TYPE = Homogeneous Collection (If Possible)
    CONCAT_ATTRS = _ansvarigPart _element _presentation _result
    MODE = Geometry - Assemble One Level
    AGGREGATE -> StringConcatenator_5
StringConcatenator_5
    ACTION = Create New Attribute
    PARM_LINE:
      <script type="text/javascript">
      @Value(_result)
      </script>
      <!DOCTYPE html>
      <html lang="en">
      <head>
      <meta charset="UTF-8">
      <title>Education create layer codes according to SB11/Trafikverket 1.0</title>
      <style>
      html { margin:0; padding:0; font-size:62.5%; }
      body { max-width:auto; min-width:auto; margin:0 auto; padding:20px 10px; font-size:14px; font-size:1.4em; }

      .grid-container {
        display: grid;
        grid-template-columns: 0.5fr 720px 0.5fr 0.5fr 600px 0.7fr;
        padding: 3px;
        grid-gap: 2px;
        overflow-x: auto;
        grid-gap: 5px;
        min-width: 1900px;
      }

      .grid-container1{
      display: grid ;
      align-items: top ;
      grid-gap: 10px;
      grid-auto-flow: column ;
      grid-auto-rows: 100% ; // play with this to change height of the children, 50% will fill half

        grid-template-columns: 0.5fr 760px 0.5fr 0.5fr 1fr 0.7fr;
        padding: 5px;
        grid-gap: 2px;
      grid-template-rows: unset;
      overflow: scroll;
      }

      .grid-item {
        outline: 1px solid gray;
      overflow:hidden;
      }

      .select2-results__options {
        min-height: 250px !important;
        overflow-y: auto !important;
        max-height: 900px !important;
      }

      .layercode {
      outline: 1px solid gray;
      padding: 5px;
      }
      /*Jstree*/
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      /*select2*/
      .select2-container{box-sizing:border-box;display:inline-block;margin:0;position:relative;vertical-align:middle}.select2-container .select2-selection--single{box-sizing:border-box;cursor:pointer;display:block;height:28px;user-select:none;-webkit-user-select:none}.select2-container .select2-selection--single .select2-selection__rendered{display:block;padding-left:8px;padding-right:20px;overflow:hidden;text-overflow:ellipsis;white-space:nowrap}.select2-container .select2-selection--single .select2-selection__clear{position:relative}.select2-container[dir="rtl"] .select2-selection--single .select2-selection__rendered{padding-right:8px;padding-left:20px}.select2-container .select2-selection--multiple{box-sizing:border-box;cursor:pointer;display:block;min-height:32px;user-select:none;-webkit-user-select:none}.select2-container .select2-selection--multiple .select2-selection__rendered{display:inline-block;overflow:hidden;padding-left:8px;text-overflow:ellipsis;white-space:nowrap}.select2-container .select2-search--inline{float:left}.select2-container .select2-search--inline .select2-search__field{box-sizing:border-box;border:none;font-size:100%;margin-top:5px;padding:0}.select2-container .select2-search--inline .select2-search__field::-webkit-search-cancel-button{-webkit-appearance:none}.select2-dropdown{background-color:white;border:1px solid #aaa;border-radius:4px;box-sizing:border-box;display:block;position:absolute;left:-100000px;width:100%;z-index:1051}.select2-results{display:block}.select2-results__options{list-style:none;margin:0;padding:0}.select2-results__option{padding:6px;user-select:none;-webkit-user-select:none}.select2-results__option[aria-selected]{cursor:pointer}.select2-container--open .select2-dropdown{left:0}.select2-container--open .select2-dropdown--above{border-bottom:none;border-bottom-left-radius:0;border-bottom-right-radius:0}.select2-container--open .select2-dropdown--below{border-top:none;border-top-left-radius:0;border-top-right-radius:0}.select2-search--dropdown{display:block;padding:4px}.select2-search--dropdown .select2-search__field{padding:4px;width:100%;box-sizing:border-box}.select2-search--dropdown .select2-search__field::-webkit-search-cancel-button{-webkit-appearance:none}.select2-search--dropdown.select2-search--hide{display:none}.select2-close-mask{border:0;margin:0;padding:0;display:block;position:fixed;left:0;top:0;min-height:100%;min-width:100%;height:auto;width:auto;opacity:0;z-index:99;background-color:#fff;filter:alpha(opacity=0)}.select2-hidden-accessible{border:0 !important;clip:rect(0 0 0 0) !important;-webkit-clip-path:inset(50%) !important;clip-path:inset(50%) !important;height:1px !important;overflow:hidden !important;padding:0 !important;position:absolute !important;width:1px !important;white-space:nowrap !important}.select2-container--default .select2-selection--single{background-color:#fff;border:1px solid #aaa;border-radius:4px}.select2-container--default .select2-selection--single .select2-selection__rendered{color:#444;line-height:28px}.select2-container--default .select2-selection--single .select2-selection__clear{cursor:pointer;float:right;font-weight:bold}.select2-container--default .select2-selection--single .select2-selection__placeholder{color:#999}.select2-container--default .select2-selection--single .select2-selection__arrow{height:26px;position:absolute;top:1px;right:1px;width:20px}.select2-container--default .select2-selection--single .select2-selection__arrow b{border-color:#888 transparent transparent transparent;border-style:solid;border-width:5px 4px 0 4px;height:0;left:50%;margin-left:-4px;margin-top:-2px;position:absolute;top:50%;width:0}.select2-container--default[dir="rtl"] .select2-selection--single .select2-selection__clear{float:left}.select2-container--default[dir="rtl"] .select2-selection--single .select2-selection__arrow{left:1px;right:auto}.select2-container--default.select2-container--disabled .select2-selection--single{background-color:#eee;cursor:default}.select2-container--default.select2-container--disabled .select2-selection--single .select2-selection__clear{display:none}.select2-container--default.select2-container--open .select2-selection--single .select2-selection__arrow b{border-color:transparent transparent #888 transparent;border-width:0 4px 5px 4px}.select2-container--default .select2-selection--multiple{background-color:white;border:1px solid #aaa;border-radius:4px;cursor:text}.select2-container--default .select2-selection--multiple .select2-selection__rendered{box-sizing:border-box;list-style:none;margin:0;padding:0 5px;width:100%}.select2-container--default .select2-selection--multiple .select2-selection__rendered li{list-style:none}.select2-container--default .select2-selection--multiple .select2-selection__clear{cursor:pointer;float:right;font-weight:bold;margin-top:5px;margin-right:10px;padding:1px}.select2-container--default .select2-selection--multiple .select2-selection__choice{background-color:#e4e4e4;border:1px solid #aaa;border-radius:4px;cursor:default;float:left;margin-right:5px;margin-top:5px;padding:0 5px}.select2-container--default .select2-selection--multiple .select2-selection__choice__remove{color:#999;cursor:pointer;display:inline-block;font-weight:bold;margin-right:2px}.select2-container--default .select2-selection--multiple .select2-selection__choice__remove:hover{color:#333}.select2-container--default[dir="rtl"] .select2-selection--multiple .select2-selection__choice,.select2-container--default[dir="rtl"] .select2-selection--multiple .select2-search--inline{float:right}.select2-container--default[dir="rtl"] .select2-selection--multiple .select2-selection__choice{margin-left:5px;margin-right:auto}.select2-container--default[dir="rtl"] .select2-selection--multiple .select2-selection__choice__remove{margin-left:2px;margin-right:auto}.select2-container--default.select2-container--focus .select2-selection--multiple{border:solid black 1px;outline:0}.select2-container--default.select2-container--disabled .select2-selection--multiple{background-color:#eee;cursor:default}.select2-container--default.select2-container--disabled .select2-selection__choice__remove{display:none}.select2-container--default.select2-container--open.select2-container--above .select2-selection--single,.select2-container--default.select2-container--open.select2-container--above .select2-selection--multiple{border-top-left-radius:0;border-top-right-radius:0}.select2-container--default.select2-container--open.select2-container--below .select2-selection--single,.select2-container--default.select2-container--open.select2-container--below .select2-selection--multiple{border-bottom-left-radius:0;border-bottom-right-radius:0}.select2-container--default .select2-search--dropdown .select2-search__field{border:1px solid #aaa}.select2-container--default .select2-search--inline .select2-search__field{background:transparent;border:none;outline:0;box-shadow:none;-webkit-appearance:textfield}.select2-container--default .select2-results>.select2-results__options{max-height:200px;overflow-y:auto}.select2-container--default .select2-results__option[role=group]{padding:0}.select2-container--default .select2-results__option[aria-disabled=true]{color:#999}.select2-container--default .select2-results__option[aria-selected=true]{background-color:#ddd}.select2-container--default .select2-results__option .select2-results__option{padding-left:1em}.select2-container--default .select2-results__option .select2-results__option .select2-results__group{padding-left:0}.select2-container--default .select2-results__option .select2-results__option .select2-results__option{margin-left:-1em;padding-left:2em}.select2-container--default .select2-results__option .select2-results__option .select2-results__option .select2-results__option{margin-left:-2em;padding-left:3em}.select2-container--default .select2-results__option .select2-results__option .select2-results__option .select2-results__option .select2-results__option{margin-left:-3em;padding-left:4em}.select2-container--default .select2-results__option .select2-results__option .select2-results__option .select2-results__option .select2-results__option .select2-results__option{margin-left:-4em;padding-left:5em}.select2-container--default .select2-results__option .select2-results__option .select2-results__option .select2-results__option .select2-results__option .select2-results__option .select2-results__option{margin-left:-5em;padding-left:6em}.select2-container--default .select2-results__option--highlighted[aria-selected]{background-color:#5897fb;color:white}.select2-container--default .select2-results__group{cursor:default;display:block;padding:6px}.select2-container--classic .select2-selection--single{background-color:#f7f7f7;border:1px solid #aaa;border-radius:4px;outline:0;background-image:-webkit-linear-gradient(top, #fff 50%, #eee 100%);background-image:-o-linear-gradient(top, #fff 50%, #eee 100%);background-image:linear-gradient(to bottom, #fff 50%, #eee 100%);background-repeat:repeat-x;filter:progid:DXImageTransform.Microsoft.gradient(startColorstr='#FFFFFFFF', endColorstr='#FFEEEEEE', GradientType=0)}.select2-container--classic .select2-selection--single:focus{border:1px solid #5897fb}.select2-container--classic .select2-selection--single .select2-selection__rendered{color:#444;line-height:28px}.select2-container--classic .select2-selection--single .select2-selection__clear{cursor:pointer;float:right;font-weight:bold;margin-right:10px}.select2-container--classic .select2-selection--single .select2-selection__placeholder{color:#999}.select2-container--classic .select2-selection--single .select2-selection__arrow{background-color:#ddd;border:none;border-left:1px solid #aaa;border-top-right-radius:4px;border-bottom-right-radius:4px;height:26px;position:absolute;top:1px;right:1px;width:20px;background-image:-webkit-linear-gradient(top, #eee 50%, #ccc 100%);background-image:-o-linear-gradient(top, #eee 50%, #ccc 100%);background-image:linear-gradient(to bottom, #eee 50%, #ccc 100%);background-repeat:repeat-x;filter:progid:DXImageTransform.Microsoft.gradient(startColorstr='#FFEEEEEE', endColorstr='#FFCCCCCC', GradientType=0)}.select2-container--classic .select2-selection--single .select2-selection__arrow b{border-color:#888 transparent transparent transparent;border-style:solid;border-width:5px 4px 0 4px;height:0;left:50%;margin-left:-4px;margin-top:-2px;position:absolute;top:50%;width:0}.select2-container--classic[dir="rtl"] .select2-selection--single .select2-selection__clear{float:left}.select2-container--classic[dir="rtl"] .select2-selection--single .select2-selection__arrow{border:none;border-right:1px solid #aaa;border-radius:0;border-top-left-radius:4px;border-bottom-left-radius:4px;left:1px;right:auto}.select2-container--classic.select2-container--open .select2-selection--single{border:1px solid #5897fb}.select2-container--classic.select2-container--open .select2-selection--single .select2-selection__arrow{background:transparent;border:none}.select2-container--classic.select2-container--open .select2-selection--single .select2-selection__arrow b{border-color:transparent transparent #888 transparent;border-width:0 4px 5px 4px}.select2-container--classic.select2-container--open.select2-container--above .select2-selection--single{border-top:none;border-top-left-radius:0;border-top-right-radius:0;background-image:-webkit-linear-gradient(top, #fff 0%, #eee 50%);background-image:-o-linear-gradient(top, #fff 0%, #eee 50%);background-image:linear-gradient(to bottom, #fff 0%, #eee 50%);background-repeat:repeat-x;filter:progid:DXImageTransform.Microsoft.gradient(startColorstr='#FFFFFFFF', endColorstr='#FFEEEEEE', GradientType=0)}.select2-container--classic.select2-container--open.select2-container--below .select2-selection--single{border-bottom:none;border-bottom-left-radius:0;border-bottom-right-radius:0;background-image:-webkit-linear-gradient(top, #eee 50%, #fff 100%);background-image:-o-linear-gradient(top, #eee 50%, #fff 100%);background-image:linear-gradient(to bottom, #eee 50%, #fff 100%);background-repeat:repeat-x;filter:progid:DXImageTransform.Microsoft.gradient(startColorstr='#FFEEEEEE', endColorstr='#FFFFFFFF', GradientType=0)}.select2-container--classic .select2-selection--multiple{background-color:white;border:1px solid #aaa;border-radius:4px;cursor:text;outline:0}.select2-container--classic .select2-selection--multiple:focus{border:1px solid #5897fb}.select2-container--classic .select2-selection--multiple .select2-selection__rendered{list-style:none;margin:0;padding:0 5px}.select2-container--classic .select2-selection--multiple .select2-selection__clear{display:none}.select2-container--classic .select2-selection--multiple .select2-selection__choice{background-color:#e4e4e4;border:1px solid #aaa;border-radius:4px;cursor:default;float:left;margin-right:5px;margin-top:5px;padding:0 5px}.select2-container--classic .select2-selection--multiple .select2-selection__choice__remove{color:#888;cursor:pointer;display:inline-block;font-weight:bold;margin-right:2px}.select2-container--classic .select2-selection--multiple .select2-selection__choice__remove:hover{color:#555}.select2-container--classic[dir="rtl"] .select2-selection--multiple .select2-selection__choice{float:right;margin-left:5px;margin-right:auto}.select2-container--classic[dir="rtl"] .select2-selection--multiple .select2-selection__choice__remove{margin-left:2px;margin-right:auto}.select2-container--classic.select2-container--open .select2-selection--multiple{border:1px solid #5897fb}.select2-container--classic.select2-container--open.select2-container--above .select2-selection--multiple{border-top:none;border-top-left-radius:0;border-top-right-radius:0}.select2-container--classic.select2-container--open.select2-container--below .select2-selection--multiple{border-bottom:none;border-bottom-left-radius:0;border-bottom-right-radius:0}.select2-container--classic .select2-search--dropdown .select2-search__field{border:1px solid #aaa;outline:0}.select2-container--classic .select2-search--inline .select2-search__field{outline:0;box-shadow:none}.select2-container--classic .select2-dropdown{background-color:#fff;border:1px solid transparent}.select2-container--classic .select2-dropdown--above{border-bottom:none}.select2-container--classic .select2-dropdown--below{border-top:none}.select2-container--classic .select2-results>.select2-results__options{max-height:200px;overflow-y:auto}.select2-container--classic .select2-results__option[role=group]{padding:0}.select2-container--classic .select2-results__option[aria-disabled=true]{color:grey}.select2-container--classic .select2-results__option--highlighted[aria-selected]{background-color:#3875d7;color:#fff}.select2-container--classic .select2-results__group{cursor:default;display:block;padding:6px}.select2-container--classic.select2-container--open .select2-dropdown{border-color:#5897fb}
      </style>

      </head>
      <body>
      <br>
      <b>Resulting layer-code </b><span id="ansvarigpartset" class="layercode">--</span><span><span id="elementset" class="layercode">------</span><span id="presentationset" class="layercode">--</span><span id="statusset" class="layercode">-</span><span id="typset" class="layercode">---</span><span id="anlaggningsdelset" class="layercode">---</span>
      <br><br>
      <b>Resulting layer-description </b><span id="ansvarigpartdescset">_</span><span> | <span id="elementdescset">_</span> | <span id="presentationdescset">_</span> | <span id="statusdescset">_</span> | <span id="typdescset">_</span> | <span id="anlaggningsdeldescset">_</span>

      <div class="grid-container">
        <div class="grid-item">
        <b><span>Ansvarig part / Responsible party</span></b>
        <br>
        <span>Required to be filled in</span>
        <br>
        <br>
      	<select id="ansvarigpartselect">
      		<option value="--">Select something</option>
      	</select>
      	<br><br>
      	<span>The layercode begins with a field that identifies who is responsible for the information that is on the layer. The tecnical area/disciplin is a larger list than those used for file names.
      This responsibility should not be confused with the technical area that is implicit in the element code, for example an architect works on similar element codes as construction</span>
        </div>
        <div class="grid-item">
          <b><span>Element</span></b>
      	<br>
      	  <span>Required to be filled in</span>
        <br>
        <br>
          <input type="text" id="searchjstreeelement" class="form-control" size="50px" placeholder="Typ to search... Min 3 characters" aria-describedby="search-addon">
      	<input type="button" class="button" value="Clear search" id="clear" style=""><input type="button" value="Expand All" onclick="$('#elementgrid').jstree('open_all');"><input type="button" value="Collapse All" onclick="$('#elementgrid').jstree('close_all');">
      	<div id="elementgrid"></div>
      	<br><br>
      	<span><b>Byggdelar/building parts: BSAB96 Buildingparts according to Trafikverkets Strukturplatsen (which is BSAB96 plus more civil classifications).</b>
      	<br>Byggdelar follows the same rules as AMA (Produktionsresultat), the context for a code is always where it is in the structure, everything above matters. So for example "45BH-- Ramper" doesn't mean it is a road exit ramp, since 45--- is HUSKOMPLETTERINGAR (ramp for houses). A road exist ramp drive way would be "31H--- Överbyggnader för vägbro", the load bearing structure for the ramp would be "21BB-- Bärverk i bro" <br>
      	A building part is a physical part of a whole idenfitied from its primary function. Building parts are idenfitied from a functional perspective, top down <span>
      	<br>
      	<br>
      	<span><b>Alternativa tabeller / Alternative tables:</b><br>  All information that can not be structured with BSAB96, for example objects that represent non-physical phenomena: contractor/tender legalities, space usage, fire restrictions for ex. There is a therefor a demand to use other klassification systems. In alternative tables Trafikverket has Tunnel and Rock with for example rock klassifications  <span>
      	<br>
      	<br>
      	<span><b>Landskapsinformation / terrain information: </b> <br>For coding of existing conditions/objects, terrain information, the following process can be used.
      	For natural occuring conditions terrain information can be used. For built existing
      	conditions you primarely use Byggdelar/Building parts or in second hand terrain information. Existing information should be coded as Existing (E) in status
        </div>
        <div class="grid-item">
          <b><span>Presentation</span></b>
      	<br>
      	  <span>Required to be filled in</span>
      	<br>
      	<br>
      	<select id="presentationselect">
      		<option value="--">Select something</option>
      	</select>
      		<br><br>
      	Presentation codes classify layers on what type of graphics they include. Graphics includes 2D/3D that describes the shape of the information but also graphics that are part of boundaries, text and measurements.
      <br><br>
      Simplified for ämnesområdesmodeller (disciplin modells) the layer that has either 2D or 3D objects that represent something and therefor has a matching element are coded as 3D (EZ) or 2D (EJ) while text in the modell is Text (T-)
      <br><br>
      For drawings there are codes that help manage multiple layers while still conforming to the requirement "Color by layer"

        </div>
      <div class="grid-item" width="100px">
           <b><span>Status</span></b>
      	<br>
      	  <span>Required to be filled in</span>
      	<br>
      	<br>
          <select id="statusselect">
      		<option value="-">Select something</option>
      	</select>
      	<br><br>
      	<span>Status describes what kind of status the building part has in the production situation. It doesn't describe past the building phase, it is a description of the production situation. Trafikverket har additions to SB11s recommendation in the form of Krav, Förslag, Utan status, Stängd. If you plan to use Krav you should consult Trafikverket first. There should be a plan how to make it appararent and accessible for the contractor when used  </span>

        </div>
      <div class="grid-item">
           <b><span>Typ / Type</span></b>
      	<br>
      	  <span>Not Required</span>
      	<br>
      	<br>
      	    <input type="text" id="searchjstreetyp" class="form-control" size="50px" placeholder="Typ to search... Min 3 characters" aria-describedby="search-addon">
      		<div id="typgrid"></div>
      	<br><br>
        Type is an addition from Tvärförbindelse Södertörn from the system design phase to SB11 on top of SB11s and Trafikverkets required fields (TDOK 2012:35 5.2.3).
        <br><br>It captures the user defined fields in SB11 (chapter 8)  Läge (placement) Ursprung (origin of information) and adds other tables. It is multiple tables in one field of 3 codes, but there is no hierarchy in the codes. It has no link to Trafikverkets Strukturplatsen
      <br><br>

        </div>
       <div class="grid-item">
          <b><span>Anläggningsdel / Construction part</span></b>
      	<br>
      	  <span>Not required</span>
      	<br>
      		<br>
              <select id="anlaggningsdelselect">
      		<option value="---">Select something</option>
      	</select>
      	<br><br>
      	Anläggningsdelar (constructionparts) is a system of dividing a road facility into parts that are then used to place installation components (komponenter).
      	As a field in the layer code, it is usually used where you have one file that include multiple anläggningsdelar as objects.
      	For example if the file is K300* (common in delområde/area 3) and includes several constructions (lets say 341,342,346),
      	the constructions can have different layers with the anläggningsdel in the end separating them and making them searchable
        </div>
       </div>

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      <br>
      <br>
      <p>Important Notice: This is a early tool to help education on layer codes according to SB11. It creates a resulting layer code and layer description and explains the attributes. Further info is in SB11 SS ISO 13567, BSAB96 and Bygghandlingar 90. <br>
      <b>At this point it should still be used in conjuction with Trafikverket SAVOIR which is the offical tool for creating layer codes </b>
      <a href="http://trafikverket.savoirdb.aec.se/web_public/index"> Link to Savoir</a></p>
      <br>Uppdaterad: @DateTimeFormat(@DateTimeNow(), %Y%m%d)



      <script type="text/javascript">
      //JStree som används för element vill inte ha mellanslag i kolumnen parent, ersätt mellanslag med _. Kolumnen id kan inte innehålla dubletter. element behöver en json med ID;Parent;Text;Beskrivning
      //Jquerymin
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      //jstree
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      //jstreegrid
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      //select2
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


      var to1 = false;

      $('#searchjstreeelement').keyup(function() {
        if (to1) {
          clearTimeout(to1);
        }
        to = setTimeout(function() {
          var v = $('#searchjstreeelement').val();
      	if(v.length > 2) {
          $('#elementgrid').jstree(true).search(v);
        }else {
        $('#elementgrid').jstree(true).search("");
        }
        }, 350);

      });

      var to2 = false;
      $('#searchjstreetyp').keyup(function() {
        if (to2) {
          clearTimeout(to2);
        }
        to2 = setTimeout(function() {
          var vv = $('#searchjstreetyp').val();
      	if(vv.length > 2) {
          $('#typgrid').jstree(true).search(vv);
        }else {
        $('#typgrid').jstree(true).search("");
        }
        }, 350);

      });


      //Lägger till elementkod som resultatkod när man väljer något i listan
      $('#elementgrid')
        // listen for event

        .on('changed.jstree', function (e, data) {
          $('#elementset').html(data.node.original.text);
      	$('#elementdescset').html(data.node.original.Beskrivning);
        })

       //Lägger till typkod som resultatkod när man väljer något i listan
      $('#typgrid')
        // listen for event

        .on('changed.jstree', function (e, data) {
          $('#typset').html(data.node.original.text);
      	$('#typdescset').html(data.node.original.Beskrivning);
        })


      $(document).ready(function() {
      /////////////////////////////////
      $("#elementgrid").jstree({
        'conditionalselect' : function (node) {
         //Only let the user select nodes that are two level down, dont let them select the root levels or vary broad top levels
          return (node.parents.length > 2 || node.original.text == "------") ? true : false;
        },
          plugins: ['search','grid','sort','conditionalselect'],
          search: {
            show_only_matches: false,
      	  close_opened_onclear: true,

          },
      	grid: {
      					columns: [
      						{width: 270, header: "Name"},
      						{width: 450, header: "Beskrivning",value: function(node){return(node.original.Beskrivning);}}
      					],
      					width: 900
      				},
          core: {
      	'multiple': false,
      	"themes": {
                          "name": false,
                          "dots": true,
                          "icons": true
                      },
            data:
      element
      }
        });

      $("#typgrid").jstree({
        'conditionalselect' : function (node) {
        //Only let the user select nodes that are one level down, dont let them select the root levels
          return (node.parents.length > 1) ? true : false;
        },
          plugins: ['search','grid','sort','conditionalselect'],
          search: {
            show_only_matches: true,
      	  close_opened_onclear: true,

          },
      	grid: {
      					columns: [
      						{width: 180, header: "Name"},
      						{width: 450, header: "Beskrivning",value: function(node){return(node.original.Beskrivning);}}
      					],
      					width: 900
      				},
          core: {
      	'multiple': false,
      	"themes": {
                          "name": false,
                          "dots": true,
                          "icons": true
                      },
            data:
      typjson
      }
        });

      });

      ///////////////////



      $("#clear").click(function () {
              $("#elementgrid").jstree("clear_search");
      		$("#searchjstreeelement").val('');
          });


      //layer code result based on selection
      $('#ansvarigpartselect').change(function() {
              var x = $(this).val();
              $('#ansvarigpartset').text(x);

      		var y = $("#ansvarigpartselect :selected").data('Beskrivning');
      		console.log(y)
              $('#ansvarigpartdescset').text(y);
          });

      $('#presentationselect').change(function() {
              var x = $(this).val();
              $('#presentationset').text(x);
      		var y = $("#presentationselect :selected").data('Beskrivning');
              $('#presentationdescset').text(y);
          });
      $('#statusselect').change(function() {
              var x = $(this).val();
              $('#statusset').text(x);
      		var y = $("#statusselect :selected").data('Beskrivning');
              $('#statusdescset').text(y);
          });

      $('#anlaggningsdelselect').change(function() {
              var x = $(this).val();

              $('#anlaggningsdelset').text(x);
      		var y = $("#anlaggningsdelselect :selected").text();
              $('#anlaggningsdeldescset').text(y);
          });

      //fancy drop down library on each dropdown
      $("#ansvarigpartselect").select2({
          width: '199px' ,
      	dropdownAutoWidth : true
      });
      $("#presentationselect").select2({
          width: '199px',
      dropdownAutoWidth : true
      });
      $("#statusselect").select2({
          width: '199px',
      dropdownAutoWidth : true
      });

      $("#anlaggningsdelselect").select2({
          width: '199px' ,
      	dropdownAutoWidth : true
      });


      //var ansvarigpartjson = $.parseJSON(ansvarigpartjson);
      //var options = $("#ansvarigpartselect");
      //$.each(ansvarigpartjson, function() {
      //    options.append(new Option(this.Kod+" "+this.Beskrivning,this.Kod,this.Beskrivning));
      //});


      //Fill the drop downs from enbedded json

      var ansvarigpartjson = $.parseJSON(ansvarigpartjson);
      $.each(ansvarigpartjson, function() {
      $("#ansvarigpartselect").append($('<option />')
          .val(this.Kod)
          .text(this.Kod+" "+this.Beskrivning)
          .data({
              Beskrivning: this.Beskrivning,
      		Kod:this.Kod
          })
      	)
      });

      var presentationjson = $.parseJSON(presentationjson);
      $.each(presentationjson, function() {
      $("#presentationselect").append($('<option />')
          .val(this.Kod)
          .text(this.Kod+" "+this.Beskrivning)
          .data({
              Beskrivning: this.Beskrivning,
      		Kod:this.Kod
          })
      	)
      });

      var statusjson = $.parseJSON(statusjson);
      $.each(statusjson, function() {
      $("#statusselect").append($('<option />')
          .val(this.Kod)
          .text(this.Kod+" "+this.Beskrivning)
          .data({
              Beskrivning: this.Beskrivning,
      		Kod:this.Kod
          })
      	)
      });



      var anlaggningsdelarjson = $.parseJSON(anlaggningsdelarjson);
      $.each(anlaggningsdelarjson, function() {
      $("#anlaggningsdelselect").append($('<option />')
          .val(this.Kod)
          .text(this.Kod+" "+this.Beskrivning)
          .data({
              Beskrivning: this.Beskrivning,
      		Kod:this.Kod
          })
      	)
      });



      </script>


      </body>
      </html>
    VAL_ATTR = text_line_data
    -> text_line (writer TEXTLINE_1)
    -> BinaryEncoder
text_line (writer TEXTLINE_1)
    attributes: text_line_data buffer
BinaryEncoder
    ATTRS_TO_ENCODE = text_line_data
    ENCODING_TYPE = Base64
    WRITE_TO_OTHER_ATTRS = No
    -> HTTPCaller_2
HTTPCaller_2
    CONNECTION_TIMEOUT_LENGTH = 60
    ERROR_ATTR = _error
    FOLLOW_REDIRECTS = FOLLOW_WITH_GET
    HTTP_METHOD = GET
    REDIRECT_AUTH = ORIGINAL_DOMAIN_ONLY
    SAVE_FILE = Attribute
    STATUS_CODE_ATTR = _http_status_code
    TARGET_ATTR = _response_body
    TARGET_ATTR_ENCODING = auto-detect
    TARGET_URL = https://api.github.com/repos/structurplatseneducation/educationtool/contents/education.html
    TRANSFER_TIMEOUT_LENGTH = 90
    USE_COOKIES = No
    VERIFY_SSL_CERTIFICATES = Yes
    -> JSONExtractor
JSONExtractor
    EXTRACT_QUERY_TABLE = sha json["sha"]
    JSON_DOCUMENT = @Value(_response_body)
    READ_FROM_FILE = NO
    EVALUATED -> StringConcatenator_6
StringConcatenator_6
    ACTION = Create New Attribute
    PARM_LINE:
      fme_basicstring:32%11%14%22%4:{
      "message":"From FME",
       "sha":"@Value(sha)",
      "content":"@Value(text_line_data)"
       }
    VAL_ATTR = _githubdata
    -> HTTPCaller
HTTPCaller
    CONNECTION_TIMEOUT_LENGTH = 60
    CUSTOM_HEADERS = Authorization;token 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 accept;application/vnd.github.v3+json
    ERROR_ATTR = _error
    FOLLOW_REDIRECTS = FOLLOW_WITH_GET
    HTTP_METHOD = PUT
    REDIRECT_AUTH = ORIGINAL_DOMAIN_ONLY
    SAVE_FILE = Attribute
    STATUS_CODE_ATTR = _http_status_code
    TARGET_ATTR = _response_body
    TARGET_ATTR_ENCODING = auto-detect
    TARGET_URL = https://api.github.com/repos/structurplatseneducation/educationtool/contents/education.html
    TRANSFER_TIMEOUT_LENGTH = 90
    UPLOAD_BODY = @Value(_githubdata)
    UPLOAD_CONTENT_TYPE = JSON (application/json)
    UPLOAD_TYPE = Specify Upload Body
    USE_COOKIES = No
    VERIFY_SSL_CERTIFICATES = Yes
    -> HTTPCaller_Output
    <REJECTED> -> HTTPCaller__Rejected_
HTTPCaller_Output: Logger
    LOG_FEATURE = LOG_ONLY
    MAXCOORDS = 20
    MAXFEATS = 20
    MESSAGE = Feature is:
    SEVERITY = INFO
HTTPCaller__Rejected_: Logger
    LOG_FEATURE = LOG_ONLY
    MAXCOORDS = 20
    MAXFEATS = 20
    MESSAGE = Feature is:
    SEVERITY = INFO
